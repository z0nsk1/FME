FME workspace proju.fmw

Parameters:
- SourceDataset_XLSXR = $(FME_MF_DIR)Sky Glow Mapping 5.3.2024\01 5.3. third_3_MB.xlsx   # Source Microsoft Excel File(s)
- DestDataset_FILEGDB = $(FME_MF_DIR)bortle.gdb   # File Geodatabase
- DestDataset_OGCKML = $(FME_MF_DIR)bortle.gdb\nelm.kml   # Destination Google KML File
- SourceDataset_XLSXR_3 = $(FME_MF_DIR)Sky Glow Mapping 5.3.2024\01 5.3. third_3_NELM.xlsx   # Source Microsoft Excel File(s)

Readers:
- XLSXR_1: XLSXR from $(SourceDataset_XLSXR) in LL-WGS84
- XLSXR_2: XLSXR from $(SourceDataset_XLSXR_3)

Writers:
- FILEGDB_1: FILEGDB to $(DestDataset_FILEGDB) in LL-WGS84
- OGCKML_1: OGCKML to $(DestDataset_OGCKML) in LL-WGS84

Bookmark: Reader Feature Types
Survey Data (reader XLSXR_1)
    attributes: GPS Coordinates (m) char(20), Distance (m) number(8,2), SQM (mag/arcsec) number(5,2), Bortle Scale number(3,1), Run Average number(5,2), Delta number(5,2), Original number(5,2), H string, I string, J string, K string, GPS Accuracy number(4,2), Notes char(12), Overall Run Average number(5,2), Road Name char(17), Road ID number(1,0), Surveyed Road Length (m) number(8,2), R string, S string, Min. Measured string, Max. Measured string, V string, W string, X string, File Name char(30), Survey Date datetime, AA char(1), AB string, AC string, AD string,
      AE string, AF string, AG string, Priority char(1), Event Code char(1), Project Description string
    -> AttributeKeeper

Bookmark: Bortle ja SQM (MB)
AttributeKeeper
    CREATE_BULK_MODE_FEATURES = NO
    KEEP_ATTRS = Bortle Scale,GPS Coordinates (m),SQM (mag/arcsec)
    -> AttributeSplitter
AttributeSplitter
    ATTR_NAME = GPS Coordinates (m)
    DELIMITER = ,
    DROP_EMPTY_PARTS = Yes
    LIST_NAME = Coordinates
    TRIM_OPTION = Both
    -> AttributeRemover
AttributeRemover
    REMOVE_ATTRS = GPS Coordinates (m)
    -> AttributeRenamer
AttributeRenamer
    ATTR_TABLE:
      RENAME_SET_DEFAULT Coordinates{0} > longitude
      RENAME_SET_DEFAULT Coordinates{1} > latitude
    KEEP_RENAMED_ONLY = no
    MISSING_INPUT_ATTRS = REMOVE
    -> VertexCreator
VertexCreator
    MEASURE_TYPE = Continuous
    MODE_NAME = Replace with Point
    XVAL = @Value(latitude)
    YVAL = @Value(longitude)
    -> ColorsForSQM
    -> ColorsForBortle
Survey Data (writer OGCKML_1)
    attributes: RGB_COLOR kml_char(200), FME_COLOR kml_char(200), HEX_COLOR kml_char(200), longitude kml_char(200), latitude kml_char(200), SQM (mag/arcsec) kml_real32, Bortle Scale kml_real32, Coordinates{} kml_char(200), color kml_char(255), AUTOCAD_COLOR kml_char(255)

Bookmark: Värien asetus (HEX)
ColorsForSQM: AttributeRangeMapper
    IN_ATTR = SQM (mag/arcsec)
    LUT = -inf,10,#b7ff8b,10,11,#FFEE00,11,12,#EDE24C,12,13,#D6E684,13,14,#BDE684,14,15,#7ADAA4,15,16,#47CC81,16,17,#5C97FD,17,18,#477FDF,18,19,#2C66CA,19,20,#114195,20,21,#101669,21,inf,#050A58,,,
    OUT_ATTR = color
    -> ColorConverterNew
ColorsForBortle: AttributeRangeMapper
    IN_ATTR = Bortle Scale
    LUT = 4,5,#000545,5,6,#06007B,6,7,#0A00C7,7,8,#5B53FF,8,inf,#BDBAFF,,,
    OUT_ATTR = color
    -> ColorConverterNew_2

Bookmark: HEX -> FME värijärjestelmä muunnos
ColorConverterNew
    Attr2Convert = color
    FromColorType = HEX
    ToColorType = FME
    -> KMLStyler
ColorConverterNew_2
    Attr2Convert = color
    FromColorType = HEX
    ToColorType = FME
    -> KMLStyler_2

Bookmark: Kartan pisteiden värjäys
KMLStyler
    COLOR = @Value(FME_COLOR)
    FILL_OPACITY = 0.4
    ICON_OPACITY = 1.0
    ICON_SCALE = 0.8
    LABEL_OPACITY = 1.0
    LABEL_SCALE = 1.0
    LABEL_VISIBILITY = Yes
    LINE_WIDTH = 1.0
    LINE_WIDTH_UNITS = Pixels (Display Units)
    OPACITY = 1.0
    STYLE_PER_FEATURE = Yes
    KMLStyled -> Survey Data (writer OGCKML_1)
KMLStyler_2
    COLOR = @Value(FME_COLOR)
    FILL_OPACITY = 0.4
    ICON_OPACITY = 1.0
    ICON_SCALE = 0.8
    LABEL_OPACITY = 1.0
    LABEL_SCALE = 1.0
    LABEL_VISIBILITY = Yes
    LINE_WIDTH = 1.0
    LINE_WIDTH_UNITS = Pixels (Display Units)
    OPACITY = 1.0
    STYLE_PER_FEATURE = Yes

Bookmark: NELM
Survey Data (reader XLSXR_2)
    attributes: GPS Coordinates (m) char(20), Distance (m) number(8,2), NELM number(4,2), Bortle Scale number(3,1), E number(5,2), Delta number(5,2), Original number(5,2), H string, I string, J string, K string, GPS Accuracy number(4,2), Notes char(12), Overall Run Average number(5,2), Road Name char(17), Road ID number(1,0), Surveyed Road Length (m) number(8,2), R string, S string, Min. Measured string, Max. Measured string, V string, W string, X string, File Name char(32), Survey Date datetime, AA char(1), AB string, AC string, AD string,
      AE string, AF string, AG string, Priority char(1), Event Code char(1), Project Description string
    -> AttributeKeeper_2
AttributeKeeper_2
    CREATE_BULK_MODE_FEATURES = NO
    KEEP_ATTRS = GPS Coordinates (m),NELM
    -> AttributeSplitter_2
AttributeSplitter_2
    ATTR_NAME = GPS Coordinates (m)
    DELIMITER = ,
    DROP_EMPTY_PARTS = Yes
    LIST_NAME = Coordinates
    TRIM_OPTION = Both
    -> AttributeRemover_2
AttributeRemover_2
    REMOVE_ATTRS = GPS Coordinates (m)
    -> AttributeRenamer_2
AttributeRenamer_2
    ATTR_TABLE:
      RENAME_SET_DEFAULT Coordinates{0} > longitude
      RENAME_SET_DEFAULT Coordinates{1} > latitude
    KEEP_RENAMED_ONLY = no
    MISSING_INPUT_ATTRS = REMOVE
    -> VertexCreator_2
VertexCreator_2
    MEASURE_TYPE = Continuous
    MODE_NAME = Replace with Point
    XVAL = @Value(latitude)
    YVAL = @Value(longitude)
    -> ColorsForSQM_2
ColorsForSQM_2: AttributeRangeMapper
    IN_ATTR = NELM
    LUT = 0,1,#b7ff8b,1,1.5,#FFEE00,1.5,2,#EDE24C,2,2.5,#D6E684,2.5,3,#BDE684,3,3.5,#7ADAA4,3.5,4,#47CC81,4,4.5,#5C97FD,4.5,5,#477FDF,5,5.5,#2C66CA,5.5,6,#114195,6,6.5,#101669,6.5,7,#050A58,,,
    OUT_ATTR = color
    -> ColorConverterNew_3
ColorConverterNew_3
    Attr2Convert = color
    FromColorType = HEX
    ToColorType = FME
    -> KMLStyler_3
KMLStyler_3
    COLOR = @Value(FME_COLOR)
    FILL_OPACITY = 0.4
    ICON_OPACITY = 1.0
    ICON_SCALE = 0.8
    LABEL_OPACITY = 1.0
    LABEL_SCALE = 1.0
    LABEL_VISIBILITY = Yes
    LINE_WIDTH = 1.0
    LINE_WIDTH_UNITS = Pixels (Display Units)
    OPACITY = 1.0
    STYLE_PER_FEATURE = Yes
    KMLStyled -> Survey Data00 (writer OGCKML_1)
Survey Data00 (writer OGCKML_1)
    attributes: RGB_COLOR kml_char(200), FME_COLOR kml_char(200), HEX_COLOR kml_char(200), longitude kml_char(200), latitude kml_char(200), NELM kml_real32, Coordinates{} kml_char(200), color kml_char(255), AUTOCAD_COLOR kml_char(255)
